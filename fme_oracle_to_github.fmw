FME workspace fme_oracle_to_github.fmw
Shutdown Tcl:
      #set git directory
      set directorio $FME_MacroValues(Directorio)
      #set git file
      set file ""
      #set git commit
      set commit $FME_MacroValues(Commit)
      #set git user
      set usuario $FME_MacroValues(UsuarioGithub)
      #set git password
      set password $FME_MacroValues(PasswordGithub)
      #set git repository
      set repositorio $FME_MacroValues(Repositorio)
      set date [clock format [clock seconds] -format {%Y%m%d%H%M%S}]

      #git-init - Create an empty Git repository or reinitialize an existing one
      exec git init $directorio
      #directorio de trabajo
      cd $directorio
      set direc [pwd]

      append commit " " $date

      #git-add - Add file contents to the index git-stage - Add file contents to the staging area
      exec git add --all
      # git-commit - Record changes to the repository
      exec git commit -m $commit

      #Add layers to the remote repository
      set dirremoto ""
      append dirremoto "https://github.com/" $usuario "/" $repositorio ".git"
      puts $dirremoto

      #Change the remote repository
      exec git remote set-url origin $dirremoto

      # GIT PUSH
      set url ""
      append url "https://" $usuario ":" $password "@github.com/" $usuario "/" $repositorio ".git"

      if { [catch { exec git push $url master } msg] } {
         puts "Resultados del push:"
         puts "Information about it: $::errorInfo"
      }

Parameters:
- Directorio =
- Commit = Actualización geoJSON desde tablas Oracle con FME.
- UsuarioGithub =   # Usuario github
- Repositorio = base_datos_geografica
- PasswordGithub =   # Password
- FeatureClassList =
- nombre_geojson = ""
- nombre_directorio:   # Tcl Script
      ## Uncomment if use disk file
      set directorio $FME_MacroValues(Directorio)
      
      append nombre_directorio $directorio
      return $nombre_directorio
- FeatureTypes:   # Python Script
      import os
      #set git directory
      #directorio de trabajo
      # GIT PULL (Pull--local drive FeatureTypesToRead)
      directorio = (FME_MacroValues['Directorio'])
      os.chdir(directorio)
      #Do the git pull - maybe like this?
      import subprocess
      process = subprocess.Popen(["git", "pull"], stdout=subprocess.PIPE)
      output = process.communicate()[0]
      
      #Get the file from a published parameter
      ListFile = (FME_MacroValues['FeatureClassList'])
      
      #Replace FME_MF_DIR with actual path, if necessary
      #(needs to be done if FeatureClassList file is in same directory
      # as the workspace. PR#37688)
      
      ## Uncomment if use disk file
      replaceThis = '$(FME_MF_DIR'
      directory = (FME_MacroValues['FME_MF_DIR'])
      if replaceThis in ListFile:
          ListFile = ListFile.replace(replaceThis,directory)
          ListFile = ListFile.replace(')','',1)
      
      #proxies = {'https': 'http://'}
      #import urllib
      
      # URL from GitHub
      #f = urllib.urlopen("https://raw2.github.com//base_datos_espacial/master/FeatureTypesToRead.txt", proxies=proxies)
      
      # File from disk
      f = open(ListFile,'r')
      
      # Read the file or URL and add each line to the featureTypes Variable
      #featureTypes = ''
      #for line in f.read().split('\n'):
      #    featureTypes += (line + " ")
      #f.close()
      
      #LECTURA DE UN ARCHIVO CON VARIAS COLUMNAS
      capas = ''
      featureTypes = ''
      lista = []
      
      for line in f:
          capas = line.split(';') # split line into parts
          lista.append(capas[0])
      
      f.close()
      #
      featureTypes = ' '.join(lista)
      
      #Return this list to the parameter
      return featureTypes

Readers:
- ORACLE8I_1: ORACLE8I

Writers:
- GEOJSON_1: GEOJSON to $(nombre_directorio)
- TEXTLINE_1: TEXTLINE to $(nombre_directorio)\fecha_actualizacion.txt

Note: Original data transformation: / CRS = 4326 / Round to 6 decimal places (11 cm precision) / Workbench IDErioja Spatial Database Export: / Dynamic Reader: / File stored in the GitHub repository / Fanout = File Name
Note: Pass a List of Tables or Layers to an FME Reader using Python Scripted Parameters
Note: Project: ORACLE --GEOJSON: / 1. Pass a List of IDErioja Tables to an FME Reader (Oracle) using Python Scripted Parameters / 2. Dynamic Writer (geoJSOn): For each Iderioja table one geoJSOn file: Dataset Fanout (Multiple files with one layer) / 3. "Directorio" parameter with GIT directory in local drive
Note: Dynamic mode: Merge Feature type / Merge Filter
.ANYTABLE (reader ORACLE8I_1)
    attributes: FNODE_ number(11,0), TNODE_ number(11,0), LPOLY_ number(11,0), RPOLY_ number(11,0), LENGTH number(24,5), AIRPORTS_ number(11,0), AIRPORTS_I number(11,0), LINE number(11,0), ADD_DATE char(11), NBTS number(11,0), FILLCHAR char(1), NAME char(12)
    -> PythonCaller_2
Note: PythonCaller: / read file
PythonCaller_2
    PYTHONSOURCE:
      import fmeobjects

      global nombre_json
      nombre_json = {}

      # Template Function interface:
      def processFeature1(feature):
      # Get the file from a published parameter
              ListFile = (FME_MacroValues['FeatureClassList'])


      #Replace FME_MF_DIR with actual path, if necessary
      #(needs to be done if FeatureClassList file is in same directory
      # as the workspace. PR#37688)

      ## Uncomment if use disk file
              replaceThis = '$(FME_MF_DIR'
              directory = (FME_MacroValues['FME_MF_DIR'])
              if replaceThis in ListFile:
                  ListFile = ListFile.replace(replaceThis,directory)
                  ListFile = ListFile.replace(')','',1)

      # File from disk
              f = open(ListFile,'r')

      #Read the file with more than one column
              capas = ''
              featureTypes = ''
              lista = []

              for line in f:

                  line.rstrip('\n')
                  capas = line.split(';') # split line into parts
                  lista.append(capas[0])
                  nombre_json[capas[0]] = capas[1].rstrip('\n') + '.json'

              f.close()
    PYTHONSYMBOL = processFeature1
    -> PythonCaller
Note: PythonCaller: / json filename
PythonCaller
    PYTHONSOURCE:
      import fmeobjects

      global nombre_json

      # Template Function interface:
      def processFeature(feature):

          capa = feature.getAttribute('fme_feature_type')
          feature.setAttribute("_nombre_geojson", nombre_json[capa])
    PYTHONSYMBOL = processFeature
    NEW_ATTRIBUTES = "_nombre_geojson "
    -> BulkAttributeRemover
Note: Remove audit attributes
Note: Regular expression thak works: / Suffix: FIELD_NAME$ / Regular expression thak doesn't works: / FIELD_NAME1$|FIELD_NAME2$
BulkAttributeRemover
    ATTR_EXP = ULTIMA_ACTUALIZACION$
    -> BulkAttributeRemover_2
BulkAttributeRemover_2
    ATTR_EXP = USUARIO_DELEGADO_DENO$
    -> BulkAttributeRemover_3
BulkAttributeRemover_3
    ATTR_EXP = USUARIO_DELEGADO$
    -> BulkAttributeRemover_4
BulkAttributeRemover_4
    ATTR_EXP = USUARIO_CONEXION$
    -> BulkAttributeRemover_5
BulkAttributeRemover_5
    ATTR_EXP = ALTA_BBDD$
    -> Reprojector
Note: AttributeExposer: / ENLACE_DOCUMENTOS / ENLACE_IMAGENES
AttributeExposer
    ATTR_LIST = ENLACE_IMAGENES,ENLACE_DOCUMENTOS,REF_IMAGENES,REF_DOCUMENTOS
    -> BulkAttributeRenamer_2
BulkAttributeRenamer_2
    REPLACE_STR = IMG
    ATTRCHOICE = All Attributes
    PATTERN_ACTION_DISP = Regular Expression Replace
    REPLACE_PATTERN = ^T[0-9][0-9][0-9]_NUMERO_IMAGENES$
    -> BulkAttributeRenamer_3
BulkAttributeRenamer_3
    REPLACE_STR = DOC
    ATTRCHOICE = All Attributes
    PATTERN_ACTION_DISP = Regular Expression Replace
    REPLACE_PATTERN = ^T[0-9][0-9][0-9]_NUMERO_DOCUMENTOS$
    -> BulkAttributeRenamer_4
BulkAttributeRenamer_4
    REPLACE_STR = URL_DOC
    ATTRCHOICE = All Attributes
    PATTERN_ACTION_DISP = Regular Expression Replace
    REPLACE_PATTERN = ^T[0-9][0-9][0-9]_URL_DOCUMENTOS$
    -> BulkAttributeRenamer_5
BulkAttributeRenamer_5
    REPLACE_STR = URL_IMG
    ATTRCHOICE = All Attributes
    PATTERN_ACTION_DISP = Regular Expression Replace
    REPLACE_PATTERN = ^T[0-9][0-9][0-9]_URL_IMAGENES$
    -> AttributeExposer_2
AttributeExposer_2
    ATTR_LIST = IMG,DOC,URL_IMG,URL_DOC
    -> Tester
Tester
    TEST_MODE = Automatic
    TEST_DESCRIPTION = ""
    BOOL_OP = OR
    TEST_CLAUSE = TEST @Value(IMG) > 0
    FAILED -> Tester_2
    PASSED -> AttributeCopier_2
AttributeCopier_2
    ATTR_LIST = URL_IMG,ENLACE_IMAGENES,""
    -> StringConcatenator_2
StringConcatenator_2
    PARM_LINE = <a target='_blank' href='@Value(URL_IMG)'>Imágenes</a>
    VAL_ATTR = REF_IMAGENES
    -> Tester_2
Tester_2
    TEST_MODE = Automatic
    TEST_DESCRIPTION = ""
    BOOL_OP = OR
    TEST_CLAUSE = TEST @Value(DOC) > 0
    PASSED -> AttributeCopier_3
    FAILED -> BulkAttributeRemover_6
AttributeCopier_3
    ATTR_LIST = URL_DOC,ENLACE_DOCUMENTOS,""
    -> StringConcatenator_3
StringConcatenator_3
    PARM_LINE = <a target='_blank' href='@Value(URL_DOC)'>Documentos</a>
    VAL_ATTR = REF_DOCUMENTOS
    -> BulkAttributeRemover_6
BulkAttributeRemover_6
    ATTR_EXP = NUMERO_IMAGENES$
    -> BulkAttributeRemover_7
BulkAttributeRemover_7
    ATTR_EXP = NUMERO_DOCUMENTOS$
    -> BulkAttributeRemover_8
BulkAttributeRemover_8
    ATTR_EXP = TAG_IMAGENES$
    -> BulkAttributeRemover_9
BulkAttributeRemover_9
    ATTR_EXP = TAG_DOCUMENTOS$
    -> NewFeatureType (writer GEOJSON_1)
Note: Dynamic Properties: / Schema Sources
NewFeatureType (writer GEOJSON_1)
    attributes: IMAGENES string, DOCUMENTOS string
Creator
    NUM = 1
    GEOMTYPE = Geometry Object
    CREATED -> TimeStamper
Note: Date file that appears with the commit
text_line (writer TEXTLINE_1)
    attributes: text_line_data buffer

Bookmark: crs: 4326
Reprojector
    DEST = EPSG:4326
    RASTER_CELL_SIZE = Preserve Cells
    STROKE_ARCS = Yes
    SOURCE = ETRS89.UTM-30N
    INTERPOLATION_TYPE_NAME = Nearest Neighbor
    REPROJECTED -> CoordinateRounder
CoordinateRounder
    ZPREC = 6
    YPREC = 6
    XPREC = 6
    ROUNDED -> AttributeExposer

Bookmark: Archivo fecha_actualizacion
TimeStamper
    FMT = XML DateTime (^Y-^m-^dT^H:^M:^S)
    TIME_ATTR = _timestamp
    -> text_line (writer TEXTLINE_1)
